FME workspace hdf downloader.fmw

Parameters:
- ProductURL = http://e4ftl01.cr.usgs.gov/MOTA/MCD43B4.005
- StartDate = 20150609111900   # Start date of download
- End_Date = 20160102111900   # End date of download
- HDF_dir = G:\Extra\MCD43B4\MCD43B4_Extra_Inputs   # Directory for HDF files

Readers:
- PATH_1: PATH from $(HDF_dir)

Note: This workbench is for downloading MODIS data from the main data pool website. It's basically a web scraper. It works by reading the catalogue pages as plain text files - capitalising on the fact that we can give a URL for a text file as well as a local filename. It parses these, works out what's required by checking dates and existence of local files, then fetches them using HTTPCallers.
Creator
    NUM = 1
    GEOMTYPE = Geometry Object
    CREATED -> AttributeCreator
AttributeCreator
    ATTR_LIST = _baseURL,$(ProductURL)
    -> FeatureReader
Note: Read the top-level product directory (containing dates) as a plain text file
FeatureReader
    ATTR_CONFLICT_RES = Use Result
    TEXTLINE_SKIP_FOOTER = 0
    ATTR_ACCUM_MODE = Merge Initiator and Result
    TEXTLINE_READ_BOTTOM_UP = No
    FEATURETYPES_RADIO = FEATURETYPES
    COMBINE_GEOM = Use Result
    TEXTLINE_READ_WHOLE_FILE_AT_ONCE = NO
    TEXTLINE_SKIP_LINES = 0
    DATASET = @Value(_baseURL)
    OUTPUT_FEATURES_DISPLAY = Based on Connections
    ATTRS_TO_EXPOSE = text_line_data
    FORMAT = TEXTLINE
    <OTHER> -> AllDatesPageLines
    <OTHER> -> StringSearcher
AllDatesPageLines: Inspector
Note: regexp match lines containing a date like xxxx.xx.xx (not actually checking it is a date, just looking at the number pattern)
StringSearcher
    MATCHED_PARTS_ATTR = _matched_parts
    REGEXP = [0-9]{4}\.[0-9]{2}\.[0-9]{2}
    STRING_TO_SEARCH = @Value(text_line_data)
    MATCHED_RESULT_ATTR = _date
    CASE = no
    MATCHED -> AttributeCreator_3
AttributeCreator_3
    ATTR_LIST = fileDate,@Value(_date),minDate,$(StartDate),maxDate,$(End_Date)
    -> DateFormatter
Note: See if the date is within the range we want
DateFormatter
    SRCFMT = %Y.%m.%d
    INVALID_DATE_VALUE = _FME_NO_OP_
    DATE_ATTR = fileDate
    FMT = %Y%m%d
    -> DateFormatter_2
DateFormatter_2
    SRCFMT = Unknown - Automatic Detection
    INVALID_DATE_VALUE = _FME_NO_OP_
    DATE_ATTR = maxDate,minDate
    FMT = %Y%m%d
    -> Tester
Tester
    TEST_DESCRIPTION = ""
    TEST_CLAUSE = TEST @Value(fileDate) BETWEEN @Value(minDate),@Value(maxDate)
    TEST_MODE = Automatic
    BOOL_OP = OR
    PASSED -> AttributeCreator_2
AttributeCreator_2
    ATTR_LIST = _dateURL,@Value(_baseURL)/@Value(_date)
    -> AttributeKeeper
AttributeKeeper
    KEEP_ATTRS = _dateURL
    -> FeatureReader_2
Note: Read the date page (contains file links) as plain text lines
FeatureReader_2
    ATTR_CONFLICT_RES = Use Result
    TEXTLINE_SKIP_FOOTER = 0
    ATTR_ACCUM_MODE = Merge Initiator and Result
    TEXTLINE_READ_BOTTOM_UP = No
    FEATURETYPES_RADIO = FEATURETYPES
    COMBINE_GEOM = Use Result
    TEXTLINE_READ_WHOLE_FILE_AT_ONCE = NO
    TEXTLINE_SKIP_LINES = 0
    DATASET = @Value(_dateURL)
    OUTPUT_FEATURES_DISPLAY = Based on Connections
    ATTRS_TO_EXPOSE = text_line_data
    FORMAT = TEXTLINE
    <OTHER> -> StringSearcher_2
Note: regexp match the name of a MODIS hdf file
StringSearcher_2
    MATCHED_PARTS_ATTR = _parts
    REGEXP = M.D....\.A[0-9]{7}\.h[0-9][0-9]v[0-9][0-9]\.[0-9]+\.[0-9]+\.hdf"
    STRING_TO_SEARCH = @Value(text_line_data)
    MATCHED_RESULT_ATTR = hdfFileName
    CASE = no
    MATCHED -> HDF_Links
    MATCHED -> StringSearcher_3
HDF_Links: Inspector [off]
Note: on the hdf line only, regexp match to get the size of the file at the end of the line as a number, maybe with decimal, followed by M or K
StringSearcher_3
    MATCHED_PARTS_ATTR = _parts
    REGEXP = ([0-9]+\.)?[0-9]+[KM] *$
    STRING_TO_SEARCH = @Value(text_line_data)
    MATCHED_RESULT_ATTR = sizeText
    CASE = no
    MATCHED -> AttributeTrimmer
AttributeTrimmer
    TRIM_TO_NONE = No
    TRIM_TYPE = Both
    SRC_ATTRS = sizeText
    TRIM_CHARS = " "
    -> StringSearcher_4
Note: regexp match to get the date (not bothering with time) that the remote file was updated
StringSearcher_4
    MATCHED_PARTS_ATTR = _parts
    REGEXP = \d\d-[A-Z][a-z]{2}-201\d
    STRING_TO_SEARCH = @Value(text_line_data)
    MATCHED_RESULT_ATTR = remoteDate
    CASE = no
    MATCHED -> DateFormatter_3
DateFormatter_3
    SRCFMT = Unknown - Automatic Detection
    INVALID_DATE_VALUE = _FME_NO_OP_
    DATE_ATTR = remoteDate
    FMT = FME Date/Time (%Y%m%d%H%M%S)
    -> SubstringExtractor_2
Note: work out the approximate remote file size in bytes (from the descriptive text, not by requesting it and using content-length)
SubstringExtractor_2
    END = -2
    RESULT_ATTR = _sizeNum
    SRC_STRING = @Value(sizeText)
    START = 0
    -> SubstringExtractor_3
SubstringExtractor_3
    END = -1
    RESULT_ATTR = _sizeUnit
    SRC_STRING = @Value(sizeText)
    START = -1
    -> AttributeValueMapper
AttributeValueMapper
    DIRECTION = Forward (Source To Destination)
    LUT = K,1024,M,1048576
    SRC = _sizeUnit
    VAL_ATTR = _sizeMult
    -> AttributeCreator_5
AttributeCreator_5
    ATTR_LIST = remoteSizeMin,@Evaluate(@floor(@Value(_sizeNum))*@Value(_sizeMult))
    -> SubstringExtractor
SubstringExtractor
    END = -2
    RESULT_ATTR = hdfFileName
    SRC_STRING = @Value(hdfFileName)
    START = 0
    -> AttributeCreator_4
AttributeCreator_4
    ATTR_LIST = hdfUrl,@Value(_dateURL)/@Value(hdfFileName),hdfLocalFile,$(HDF_dir)/@Value(hdfFileName)
    -> FileExistenceChecker
Note: See if we have already got this file
FileExistenceChecker
    Input = @Value(hdfLocalFile)
    Does_Not_Exist -> ModuloCounter
    Exists -> FeatureMerger [input 1] [off]
    Does_Not_Exist -> FileExistenceChecker_Does_Not_Exist
FileExistenceChecker_Does_Not_Exist: Inspector
PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> FeatureMerger [input 2]
Note: If we've already got it attach the information about the local file
FeatureMerger
    PROCESS_DUPS = No
    JOIN_KEYS = @Value(hdfFileName) @Value(path_filename) AUTO
    ATTR_CONFLICT_RES = Use Requestor
    IGNORE_NULLS = No
    SUPPLIERS_FIRST = No
    MERGE_TYPE = Attributes Only
    ATTR_ACCUM_MODE = Merge Supplier
    MERGED -> Tester_2
Note: see if the remote one is bigger (maybe a previous failed download) - currently we check if it's below 4k too i.e. totally failed and just recorded a data error warning or something. / Also see if the remote file is more recent than our one. / If either is true then re-download.
Tester_2
    TEST_DESCRIPTION = ""
    TEST_CLAUSE:
      TEST @Value(remoteSizeMin) > @Value(path_filesize)
      TEST @Value(path_filesize) < 4096
      TEST @Value(remoteDate) > @Value(path_modified_date)
    TEST_MODE = Automatic
    COMPOSITE_TEST = "(1 AND 2) OR 3"
    BOOL_OP = COMPOSITE
    PASSED -> ModuloCounter
    PASSED -> File_Exists_But_Maybe_Wrong
Note: Split downloads into 4 paths for speed: currently disabled as not sure if this actually helps or if the http callers are blocking...? Set count max to 4 to try.
ModuloCounter
    DOMAIN = modcounter
    MOD = 1
    CNT_ATTR = _modulo_count
    -> TestFilter
TestFilter
    DEFAULT_VALUE = <UNFILTERED>
    TEST_LIST = BOOL_OP,OR,COMPOSITE_TEST,<Unused>,TEST_CLAUSE,"TEST @Value(_modulo_count) = 0",0,BOOL_OP,OR,COMPOSITE_TEST,<Unused>,TEST_CLAUSE,"TEST @Value(_modulo_count) = 1",1,BOOL_OP,OR,COMPOSITE_TEST,<Unused>,TEST_CLAUSE,"TEST @Value(_modulo_count) = 2",2,BOOL_OP,OR,COMPOSITE_TEST,<Unused>,TEST_CLAUSE,"TEST @Value(_modulo_count) = 3",3
    3 -> HTTPCaller_4
    2 -> HTTPCaller_3
    1 -> HTTPCaller_2
    0 -> HTTPCaller
HTTPCaller
    USE_COOKIES = No
    FILE_PATH_ATTR = _response_file_path
    TRANSFER_TIMEOUT_LENGTH = 0
    OUTPUT_FILENAME = @Value(hdfLocalFile)
    STATUS_CODE_ATTR = _http_status_code
    FOLLOW_REDIRECTS = Yes
    TARGET_URL = @Value(hdfUrl)
    SAVE_FILE = File
    VERIFY_SSL_CERTIFICATES = Yes
    RESPONSE_HEADER_LIST_ATTR = _headers
    HTTP_METHOD = GET
    SAVE_MULTI = No
    ERROR_ATTR = _error
    CONNECTION_TIMEOUT_LENGTH = 0
    -> Downloads_Apparently_Successful
    <Rejected> -> Logger
HTTPCaller_2
    USE_COOKIES = No
    FILE_PATH_ATTR = _response_file_path
    TRANSFER_TIMEOUT_LENGTH = 0
    OUTPUT_FILENAME = @Value(hdfLocalFile)
    STATUS_CODE_ATTR = _http_status_code
    FOLLOW_REDIRECTS = Yes
    TARGET_URL = @Value(hdfUrl)
    SAVE_FILE = File
    VERIFY_SSL_CERTIFICATES = Yes
    RESPONSE_HEADER_LIST_ATTR = _headers
    HTTP_METHOD = GET
    SAVE_MULTI = No
    ERROR_ATTR = _error
    CONNECTION_TIMEOUT_LENGTH = 0
    <Rejected> -> Logger
    -> Downloads_Apparently_Successful
HTTPCaller_3
    USE_COOKIES = No
    FILE_PATH_ATTR = _response_file_path
    TRANSFER_TIMEOUT_LENGTH = 0
    OUTPUT_FILENAME = @Value(hdfLocalFile)
    STATUS_CODE_ATTR = _http_status_code
    FOLLOW_REDIRECTS = Yes
    TARGET_URL = @Value(hdfUrl)
    SAVE_FILE = File
    VERIFY_SSL_CERTIFICATES = Yes
    RESPONSE_HEADER_LIST_ATTR = _headers
    HTTP_METHOD = GET
    SAVE_MULTI = No
    ERROR_ATTR = _error
    CONNECTION_TIMEOUT_LENGTH = 0
    -> Downloads_Apparently_Successful
    <Rejected> -> Logger
HTTPCaller_4
    USE_COOKIES = No
    FILE_PATH_ATTR = _response_file_path
    TRANSFER_TIMEOUT_LENGTH = 0
    OUTPUT_FILENAME = @Value(hdfLocalFile)
    STATUS_CODE_ATTR = _http_status_code
    FOLLOW_REDIRECTS = Yes
    TARGET_URL = @Value(hdfUrl)
    SAVE_FILE = File
    VERIFY_SSL_CERTIFICATES = Yes
    RESPONSE_HEADER_LIST_ATTR = _headers
    HTTP_METHOD = GET
    SAVE_MULTI = No
    ERROR_ATTR = _error
    CONNECTION_TIMEOUT_LENGTH = 0
    <Rejected> -> Logger
    -> Downloads_Apparently_Successful
Downloads_Apparently_Successful: Inspector
Note: Ensure we log any that fail. Just rerun the workbench until none come through here,
Logger
    MAXFEATS = 1000000
    MESSAGE = Rejected feature is:
    MAXCOORDS = 20
    LOGGED -> Downloads_Rejected
Downloads_Rejected: Inspector
File_Exists_But_Maybe_Wrong: Inspector

FME custom transformer FileExistenceChecker
This transformer checks if input file paths or directories exist and routes features accordingly.
You can set the "Input File Path" parameter to an attribute or a string.
Copyright (c) 2013 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- Input =   # Input File Path

Input (input)
    -> AttributeCreator
Note: Get parameter value
AttributeCreator
    ATTR_LIST = FEC_FullPath,$(Input)
    NUM_PRIOR_FEATURES = 0
    NUM_SUBSEQUENT_FEATURES = 0
    -> PythonCaller
Note: Use OS and zipfile libraries to / check if file exists
PythonCaller
    NEW_ATTRIBUTES = FEC_exists
    PYTHONSOURCE:
      import fmeobjects
      import os
      import zipfile

      def processFeature(feature):

         # Get input path attribute
         fullpath=feature.getAttribute("FEC_FullPath")

         # Check if the file exists
         if os.path.exists(fullpath):
            feature.setAttribute("FEC_exists","Yes")
         # if not, try checking inside a zip file
         else:
            fullpath = fullpath.replace("\\","/")
            idx = fullpath.find(".zip")
            if idx > -1:
                zipPath = fullpath[:idx+4]
                pathInZip = fullpath[idx+5:]    #i.e. .zip/
                try:
                    with zipfile.ZipFile(zipPath, 'r') as f:
                        if isinstance(f.getinfo(pathInZip),zipfile.ZipInfo):
                            feature.setAttribute("FEC_exists","Yes")
                            return
                except KeyError:
                    pass
            # not found in a zipfile or in filesystem - does not exist
            feature.setAttribute("FEC_exists","No")
    PYTHONSYMBOL = processFeature
    -> Tester
Note: PASSED=File exists
Tester
    TEST_DESCRIPTION = ""
    TEST_CLAUSE = TEST @Value(FEC_exists) = Yes
    TEST_MODE = Automatic
    BOOL_OP = OR
    PASSED -> AttributeRemover
    FAILED -> AttributeRemover_2
Exists (output)
Does_Not_Exist (output)

Bookmark: Cleanup
AttributeRemover
    REMOVE_ATTRS = FEC_FullPath,FEC_exists
    -> Exists (output)
AttributeRemover_2
    REMOVE_ATTRS = FEC_FullPath,FEC_exists
    -> Does_Not_Exist (output)
